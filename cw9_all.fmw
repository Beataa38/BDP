FME workspace cw9_all.fmw

Parameters:
- DestDataset_GEODATABASE_FILE =
- DestDataset_POSTGIS_RASTER =
- SourceDataset_GEOTIFF =
- SourceDataset_GEOTIFF_3 =
- SourceDataset_POSTGIS_RASTER =
- SourceDataset_POSTGIS_RASTER_4 =
- SourceDataset_SHAPEFILE_4 =

Readers:
- GEOTIFF_1: GEOTIFF from $(SourceDataset_GEOTIFF)
- SHAPEFILE_1: SHAPEFILE from $(SourceDataset_SHAPEFILE_4)
- GEOTIFF_2: GEOTIFF from $(SourceDataset_GEOTIFF_3)
- POSTGIS_RASTER_2: POSTGIS_RASTER from $(SourceDataset_POSTGIS_RASTER)
- POSTGIS_RASTER_3: POSTGIS_RASTER from $(SourceDataset_POSTGIS_RASTER_4)

Writers:
- GEODATABASE_FILE_1: GEODATABASE_FILE to $(DestDataset_GEODATABASE_FILE) in LL84
- POSTGIS_RASTER_1: POSTGIS_RASTER to $(DestDataset_POSTGIS_RASTER)

Note: Reader with region of Scotland and Wales.
scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> AttributeFilter
Note: Choose only South Wales region by number.
AttributeFilter
    ATTR_NAME = NUMBER
    ATTR_VALUES = <Empty>,<Missing>,<Null>,<Unfiltered>,1626,1627,1628
    1626 -> SpatialFilter_4 [Filter]
    1626 -> Dissolver
    1627 -> SpatialFilter_4 [Filter]
    1627 -> Dissolver
    1628 -> SpatialFilter_4 [Filter]
    1628 -> Dissolver
Note: Merge three polygons in one.
Dissolver
    ACCUM_INPUT_ATTRS = Use Attributes From One Feature
    CLEANING_TOLERANCE = Automatic
    CONNECT_Z_MODE = First Wins
    DEAGGREGATE_INPUT = Yes
    AREA -> Clipper [CLIPPER]
Note: Reader with all tifs.
GEOTIFF (reader GEOTIFF_1)
    -> Reprojector
Note: Change coord system to WGS84.
Reprojector
    DEST = LL84
    INTERPOLATION_TYPE_NAME = Nearest Neighbor
    RASTER_CELL_SIZE = Preserve Cells
    RASTER_TOLERANCE = 0.0
    REPROJECTED -> RasterExtentsCoercer
Note: Extents of raster.
RasterExtentsCoercer
    EXTENTS_TYPE = Raster Extents
    EXTENTS -> AttributeExposer
Note: Take every tif file to read metadata in next step.
AttributeExposer
    ATTR_LIST = fme_dataset
    -> FilePropertyExtractor
Note: Read metadata.
FilePropertyExtractor
    FMT = FME Date/Time (%Y%m%d%H%M%S)
    PATH = @Value(fme_dataset)
    -> AttributeCreator
Note: Create atribute NewName from name and file size.
AttributeCreator
    ATTR_TABLE = SET_TO NewName = @Value(fme_basename)_@Value(_file_size)
    -> Extents (writer GEODATABASE_FILE_1)
Note: Writer Feature class "Extents" to the geodatabase "Resoults".
Extents (writer GEODATABASE_FILE_1)
    attributes: NewName char(200)
Note: Reader to see results from table "Exports"
Exports (reader POSTGIS_RASTER_2)
Note: Reader with all tifs.
GEOTIFF (reader GEOTIFF_2)
    -> SpatialFilter_4 [Candidate]
Note: Choose only rasters which intersect with polygons.
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CLIPPEE]
Note: Clip rasters to poligon extend.
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> RasterPaletteResolver
Note: Change to type great for database.
RasterPaletteResolver
    -> Exports (writer POSTGIS_RASTER_1)
Note: Export data to table "Exports" to database "cw9" in PostGIS.
Exports (writer POSTGIS_RASTER_1)
Note: Empty table which will be fill by sql result.
Creator
    GEOMTYPE = Geometry Object
    NUM = 1
    CREATED -> SQLExecutor [INITIATOR]
Note: Sql querry with ST_Union
SQLExecutor
    COMBINE_ATTRS = Result Attributes Only
    COMBINE_GEOM = Initiator Geometry Only
    COORDSYS = LL84
    DATASET = cw9
    FORMAT = POSTGIS_RASTER
    POSTGIS_RASTER_NAMED_CONNECTION = cw9
    POSTGIS_RASTER_QUERY_FEATURE_TYPES_FOR_MERGE_FILTERS = Yes
    POSTGIS_RASTER_READER_META_ATTRIBUTES = fme_basename
    POSTGIS_RASTER_READ_TIME_WITH_TIMEZONE = Yes
    SQL_STATEMENT = CREATE TABLE public."tab_raster" AS SELECT ST_UNION(rast) AS rast FROM public."Exports";
Note: Reader to see results from table "tab_raster"
tab_raster (reader POSTGIS_RASTER_3)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- FMT =
- PATH =

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
